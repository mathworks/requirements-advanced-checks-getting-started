# MW_CruiseControl

## #1: Interface
All interface requirements

### #2: Enable/Disable Switch
The controller shall have an On/Off Switch to enable/disable the operation of the cruise control system.

### #3: Set Speed/Decelerate Button
The controller shall have an input button to:
- set the target speed to the current vehicle speed when the cruise control is not engaged (active)
- decelerate (reduce) the target speed when the cruise control is engaged (active)

### #4: Resume Speed/Accelerate Button
The controller shall have an input button to:
- set the target speed to last acceptable target speed when the cruise control is not engaged (active)
- accelerate (increase) the target speed when the cruise control is active

### #5: Vehicle Speed Input
The controller shall have a vehicle speed input to be used by the target speed algorithm.

### #6: Vehicle Brake Input
The controller shall have a vehicle brake input to indicate when the driver has applied the brake pedal.

### #8: Engaged (active) Output
The controller shall have an output signal to indicate that the controller is engaged (active) .

### #9: Target Speed Output
The controller shall have an output signal to indicate that the target speed of the controller.

### #35: Cancel Switch
The controller shall have a Cancel Switch to disengage the operation of the cruise control system.

## #10: Functional
All non-safety functional requirements

### #14: Disabled (off) during start-up
Initial state of cruise control system shall be disabled.

### #15: Not engaged with enabling (on)
The cruise control system shall not be initially engaged with enabling.

### #16: Disengaged (not active) when disabled (off)
The cruise control system shall disengage with disabling.

### #17: Initial transition from disengaged (inactive) to engaged (active) only with “Set Speed” input after enabling (on)
The cruise control shall only transition to engaged (active) the first time after the system has been enabled with a “Set Speed” input. Target speed will be set to current vehicle speed.

### #18: “Resume” input ignored until the initial transition from disengaged (inactive) to engaged (active)
The cruise control shall ignore the “Resume” input until the initial transition to engaged (active) the first time after the system has been enabled.

### #19: Subsequent transition from disengaged (inactive) to engaged (active) with “Set Speed” input while enabled (on)
The cruise control shall transition to engaged (active) from disengaged with a “Set Speed” input when the system is enabled.

### #20: Subsequent transition from disengaged (inactive) to engaged (active) with “Resume” input while enabled (on)
The cruise control shall transition to engaged (active) from disengaged after the initial transition to engaged (active).

### #21: “Accelerate” input increases target speed only when engaged (active)
The target speed of the cruise control system shall increase by (1 mph, up to the limit) for the “Accelerate” input only when engaged. The “Accelerate” input is ignored when disengaged.

### #22: “Decelerate” input decreases target speed only when engaged (active)
The target speed of the cruise control system shall decrease by (1 mph, down to the limit) for the “Decelerate” input only when engaged. The “Decelerate” input is ignored when disengaged.

### #34: Cancel will return speed control to driver
Pressing the Cancel switch will immediately deactivate the cruise controller and return full control to the driver.

## #25: Safety
All safety derived functional requirements

### #26: Vehicle braking will transition system to disengaged (inactive) when engaged (active)
The cruise control system shall transition to disengaged from engaged when a braking event has occurred.

### #27: Transition to engaged (active) will only be permitted for vehicle speeds between 20 and 90 mph
The cruise control system target speed shall not transition to engaged unless the current vehicle speed is between 20 and 90 mph for safe operation.

### #28: Transition to disengaged (inactive) when vehicle speed is outside the limits of 20 to 90 mph
The cruise control system target speed shall transition to disengaged when the current vehicle speed is outside the limits of 20 to 90 mph for safe operation.

### #29: Target speed will be limited between 20 and 90 mph
The cruise control system target speed shall be limited between 20 and 90 mph for safe operation.

## #30: Justifications

### #31: Functional heading

### #32: Interface heading
